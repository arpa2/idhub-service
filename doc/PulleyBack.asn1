-- The PulleyBack module defines that command format that is sent from the
-- Pulley backend, through Quick DER, over AMQP 1.0 or other transports,
-- to components that should respond to updates in LDAP configuration.
--
-- The resulting protocol is simple and can be quickly turned into local
-- configuration changes, possibly after mapping back to the same API
-- as the SteamWorks Pulley defines for its backend - in which case this
-- protocol collates and proxies transactions from the Pulley to any
-- number of following hosts that it coordinates, all in one transaction.
--
-- This could be a serious alternative for the function for which we devised
-- the SteamWorks Shaft component - namely, to retain a consistent per-site
-- configuration and yet configurat various components.
--
-- From: Rick van Rein <rick@openfortress.nl>


-- TODO: There is nothing to check synchronicity between sender and receiever
-- TODO: We could assign queriable OCTET STRING identifiers to commits


PulleyBack DEFINITIONS EXPLICIT TAGS ::=

BEGIN

-- PulleyVersionInfo can be used at any place to select a
-- target protocol by OID, and its protocol version as an
-- integer number.  This structure can be matched literally
-- when sent in a canonical format such as DER or CER, but
-- keep in mind that in-depth analysis is required for
-- other on-the-wire encodings, such as BER, XML and JSON.
--
-- The range over which this version info applies is
-- any data structure following it in the same transmission,
-- ending at the next PulleyVersionInfo.  So this field
-- can be used to send alternatives, or merely to require
-- the recipient's agreement.
--
-- The txstate is absent when the initial state is an
-- empty configuration.  Note that all receivers should
-- be able to restart from the empty configuration, so
-- it will then match every backend, but senders will
-- usually prefer to work with a better matching recipient.
-- In terms of comparison rules, the contents of the
-- IMPLICIT SEQUENCE can be matched by a receiver where
-- the length to match is determined by the sender.
--
PulleyVersionInfo ::= [APPLICATION 0] IMPLICIT SEQUENCE {
	context [0] OID,
	version [1] INTEGER,
	txstate [2] OCTET STRING OPTIONAL
}

-- PulleyCommands add or delete tuples in a target set
-- namely the values that are provided, also for delete.
--
PulleyCommand ::= SEQUENCE {
	target [0] IA5STRING,
	change [1] ENUMERATED {
			del-tuple(0),
			add-tuple(1)
	},
	values [2] SEQUENCE OF OCTET STRING
}

-- PulleyTransactions combine any number of PulleyCommands
-- into one overall change; it is autocommitted by default,
-- but when prepare is TRUE, it will instead wait for a
-- separate commit or rollback message.
--
PulleyTransaction ::= [APPLICATION 1] IMPLICIT SEQUENCE {
	prestate [0] OCTET STRING,
	commands [1] SEQUENCE OF PulleyCommand
}

-- PulleySecondPhase is the outcome of a two-phase commit
-- transaction, which usually involves multiple recipients
-- that all need to succeed in preparing before a light
-- commit can be made out of the preparation; if one fails,
-- the second phase will instead be a rollback
--
PulleySecondPhase ::= [APPLICATION 2] IMPLICIT SEQUENCE {
	tx-result [0] ENUMERATED {
		prepare(0),
		commit(1),
		rollback(2)
	},
	poststate [1] OCTET STRING
}

-- Assume a transport that accepts any message size, and group
-- many changes together in one message.  This would provide a
-- logical unit of work, and be helpful with acceptance and
-- rejection of the work.
--
PulleyBackMessage ::= [APPLICATION 10] IMPLICIT SEQUENCE {
	--
	-- We always start with version information, but only
	-- one.
	--
	-- Upon receiving a bad version, the recipient ignores
	-- the message but, having taken it in and thereby
	-- made it possible for others to pick it up, sends a
	-- result which enumerates all the versions it is
	-- willing to entertain.
	--
	-- This procedure is not required for all transports;
	-- in AMQP 1.0 it is possible to not accept a message
	-- that a receiver has been considering.  This allows
	-- other recipients, perhaps running another version
	-- of the protocol, to take in the message.  Relying
	-- on that can be enough to support graceful changes
	-- to protocol versions, by running tools in parallel
	-- attached to the same transport infrastructure.
	--
	version [0] PulleyVersionInfo,
	payload [1] CHOICE {
		--
		-- Ask for a client that can start from the
		-- transaction state and other version info.
		--
		-- This field is TRUE when clients are
		-- requested to propose alternatives that
		-- represent their version information.
		--
		inquire [10] BOOLEAN,
		--
		-- Use decision to relay commit or rollback,
		-- leaving no (more) choice to the recipient.
		-- There will be no response from the receiver.
		--
		enforce [11] PulleySecondPhase --commit or rollback--,
		--
		-- Use propose to relay commands and request a
		-- final action on them.  The recipient has a
		-- choice in whether it will comply, and it will
		-- send a response to relay its suggestion.
		--
		-- The restart flag indicates that the transaction
		-- starts from an empty situation.  This may be
		-- used when the sender and receiver have lost
		-- sync.
		--
		propose [12] SEQUENCE {
			restart [20] BOOLEAN DEFAULT FALSE,
			actions [21] PulleyTransaction,
			request [22] PulleySecondPhase --commit or prepare--
		}
	}
}

PulleyBackResults ::= [APPLICATION 11] IMPLICIT SEQUENCE {
	--
	-- Since a response may indicate incompatibility with
	-- a sender's versions, it ought to contain a complete
	-- set of available versions.  The sender can then
	-- exhaustively search for overlap.
	--
	-- It is possible to reduce the set to just one version
	-- that has shown to work between the two parties;
	-- specifically, when such a version is mentioned in
	-- the message for which this provides the results.
	--
	versions SET OF PulleyVersionInfo --not empty--,
	--
	-- When a proposal was sent, the recipient should
	-- respond with what it believes is necessary as the
	-- next step.
	--
	response PulleySecondPhase --commit or rollback--
}

-- PulleyBack frames may be transported over various transports:
--   * TCP can prefix frames with a DER header or 32-bit length
--   * AMQP 1.0 can hold any size of message (same for 0-9-1)
--   * SCTP has B/E flags to recombine fragmented user messages
--
PulleyBackTransportUnit ::= CHOICE {
	master-to-slave PulleyBackMessage,
	slave-to-master PulleyBackResults
}

END
